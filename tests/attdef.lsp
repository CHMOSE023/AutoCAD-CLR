; 造一个带属性定义的图块“房间号”：矩形 + 两个属性（NO、AREA），供 blocks 测试插入时补建属性
(entmake '((0 . "BLOCK") (2 . "ROOMTAG") (70 . 2) (10 0.0 0.0 0.0)))
(entmake '((0 . "LWPOLYLINE") (100 . "AcDbEntity") (100 . "AcDbPolyline") (90 . 4) (70 . 1)
           (10 -600.0 -300.0) (10 600.0 -300.0) (10 600.0 300.0) (10 -600.0 300.0)))
(entmake '((0 . "ATTDEF") (10 -500.0 0.0 0.0) (40 . 200.0) (1 . "000") (3 . "房间号") (2 . "NO") (70 . 0)))
(entmake '((0 . "ATTDEF") (10 -500.0 -250.0 0.0) (40 . 150.0) (1 . "0") (3 . "面积") (2 . "AREA") (70 . 0)))
(entmake '((0 . "ENDBLK")))
